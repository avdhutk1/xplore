module examples {
    yang-version 1;
    namespace "urn:opendaylight:params:xml:ns:yang:examples";
    prefix "examples";

    revision "2015-01-05" {
        description "Initial revision of examples model";
    }

}
